(vl-load-com)

(defun vl-getattributevalue ( blk tag )
    ;(setq tag (strcase tag))
    (vl-some '(lambda ( att ) (if (= tag (strcase (vla-get-tagstring att))) (vla-get-textstring att))) (vlax-invoke blk 'getattributes))
)

(defun vl-setattributevalue ( blk tag val )
    ;(setq tag (strcase tag))
    (vl-some
       '(lambda ( att )
            (if (= tag (strcase (vla-get-tagstring att)))
                (progn (vla-put-textstring att val) val)
            )
        )
        (vlax-invoke blk 'getattributes)
    )
)

(defun c:ptt()
	(setq acadObj (vlax-get-acad-object))
	(setq doc (vla-get-ActiveDocument acadObj))
	(setq ssets (vla-get-selectionsets doc))
	
	(setq flag nil)
	(vlax-for item ssets
		(if (= (vla-get-name item) "2SHEET")
			(setq flag T)
		)
	)
	(if flag
		(vla-delete (vla-item ssets "2SHEET"))
	)
	(setq flag nil)
	(vlax-for item ssets
		(if (= (vla-get-name item) "1SHEET")
			(setq flag T)
		)
	)
	(if flag
		(vla-delete (vla-item ssets "1SHEET"))
	)
	(setq viewports (vla-Add (vla-get-SelectionSets doc) "2SHEET"))
	(vla-SelectOnScreen viewports)

	(setq template_sheet (vla-Add (vla-get-SelectionSets doc) "1SHEET"))
	(vla-SelectOnScreen template_sheet)
	
	(setq Xoffset (- 36.8245))
	(setq Yoffset (- 119.2471))
	(setq sheetXsize 841)
	(setq sheetYsize 594)
	(setq tempsheet (vla-Item template_sheet 0))
	(setq vpnumber (vla-get-Count viewports))
	(vla-put-ConfigName (vla-get-ActiveLayout doc) "AutoCAD PDF (High Quality Print)2.pc3")
	(setq currentPlot (vla-get-Plot doc))
	
	(setq index 0)
	(while (< index vpnumber)
		(setq tempsheetcoord (vla-get-InsertionPoint tempsheet))
		(setq vpcurrent (vla-Item viewports index))
		(setq vpcurrentcoord (vla-get-InsertionPoint vpcurrent))
		(vla-Move tempsheet tempsheetcoord vpcurrentcoord)
		(vla-Move tempsheet (vlax-3D-point 0 0 0) (vlax-3D-point Xoffset Yoffset 0))
		
		(setq blk vpcurrent)
		(setq tag "N")
		(setq ttt (vl-getattributevalue blk tag))
		
		(setq blk tempsheet)
		(setq tag "PAGE")
		(vl-setattributevalue blk tag ttt)
		
		(setq tempsheetinsertpoint (vlax-safearray->list (vlax-variant-value (vla-get-InsertionPoint tempsheet))))
		(setq tempsheetinsertX (nth 0 tempsheetinsertpoint))
		(setq tempsheetinsertY (nth 1 tempsheetinsertpoint))
		(setq plotXcoord (+ sheetXsize (nth 0 tempsheetinsertpoint)))
		(setq plotYcoord (+ sheetYsize (nth 1 tempsheetinsertpoint)))
		(setq lowerpoint (vlax-make-safearray vlax-vbDouble '(0 . 1)))
		(vlax-safearray-put-element lowerpoint 0 tempsheetinsertX)
		(vlax-safearray-put-element lowerpoint 1 tempsheetinsertY)
		(setq upperpoint (vlax-make-safearray vlax-vbDouble '(0 . 1)))
		(vlax-safearray-put-element upperpoint 0 plotXcoord)
		(vlax-safearray-put-element upperpoint 1 plotYcoord)
		(vla-SetWindowToPlot (vla-get-ActiveLayout doc) lowerpoint upperpoint)
		(vl-cmdf "_.DELAY" 200)
		
		(vla-put-PlotType (vla-get-ActiveLayout doc) acWindow)
		(setq plotFileName (strcat "PRANCHA " ttt ))
		(vla-PlotToFile currentPlot plotFileName)
		; (vla-DisplayPlotPreview (vla-get-Plot doc) acFullPreview)
		; (vl-cmdf "_.DELAY" 1000)
		
		(setq index (+ index 1))
	)
	(vla-Delete template_sheet)
	(vla-Delete viewports)
)
